ModTracker DEFINITIONS IMPLICIT TAGS ::=
BEGIN

IpAdd   ::= PrintableString

ErlangModule    ::= PrintableString
Second          ::= INTEGER

CommandId       ::= INTEGER
CommandMsg      ::= PrintableString

GroupName       ::= PrintableString (SIZE (0..50))
PermConf        ::= SEQUENCE {
    read        SEQUENCE OF GroupName,
    write       SEQUENCE OF GroupName
}

TargetId        ::= PrintableString (SIZE (0..50))
TargetHostname  ::= PrintableString (SIZE (0..50))
TargetSysname   ::= PrintableString (SIZE (0..50))
TargetTags      ::= SEQUENCE OF TargetTag
TargetTag       ::= PrintableString (SIZE (0..50))
TargetInfoType  ::= ENUMERATED {create(0), delete(1), update(2)}

Property    ::= SEQUENCE {
    key     PrintableString,
    value   PrintableString
}

Properties  ::= SEQUENCE OF Property

ProbeId         ::= INTEGER
ProbeName       ::= PrintableString (SIZE (0..30))
ProbeMod        ::= PrintableString (SIZE (0..30))
ProbeStatus     ::= PrintableString (SIZE (0..15))
ProbeType       ::= ENUMERATED {fetch(0), status(1)}
ProbeInfoType   ::= ENUMERATED {create(0), delete(1), update(2)}
ProbeValue      ::= INTEGER
ProbeStep       ::= Second
ProbeTimeout    ::= INTEGER
ProbeTimeoutWait    ::= Second
ProbeInspectors ::= SEQUENCE OF ErlangModule
ProbeRRDCreate  ::= PrintableString
ProbeRRDUpdate  ::= PrintableString
ProbeRRDGraph   ::= PrintableString

Inspector   ::= SEQUENCE {
    module  ErlangModule,
    conf    PrintableString
}
Inspectors  ::= SEQUENCE OF Inspector

Logger      ::= SEQUENCE {
    module  ErlangModule,
    conf    PrintableString
}
Loggers     ::= SEQUENCE OF Logger

ProbeConf       ::= SEQUENCE {
    name        ProbeName,
    type        ProbeType
}

FileData        ::= OCTET STRING

ProbeInfo   ::= SEQUENCE {
    channel     TargetId,
    probeId     ProbeId,
    name        ProbeName,
    permissions PermConf,
    probeMod    ErlangModule,
    probeConf   PrintableString,
    status      ProbeStatus,
    timeout     ProbeTimeout,
    step        ProbeStep,
    type        ProbeType,
    inspectors  Inspectors,
    loggers     Loggers,
    properties  Properties,
    active      INTEGER,
    -- snmpOids    SEQUENCE OF OID
    infoType    ProbeInfoType
}

ProbeActivity ::= SEQUENCE {
    channel     TargetId,
    probeId     ProbeId,
    timestamp   INTEGER,
    state       PrintableString,
    returnStatus PrintableString,
    textual     PrintableString
}

KeyVal      ::= SEQUENCE {
    key PrintableString,
    val INTEGER
}

ProbeReturn ::= SEQUENCE {
    channel         TargetId,
    probeId         ProbeId,
    status          ProbeStatus,
    originalReply   PrintableString,
    timestamp       INTEGER,
    keysVals        SEQUENCE OF KeyVal
}

ProbeModuleInfo ::= SEQUENCE {
    name        PrintableString,
    info        PrintableString
}

ProbeDump   ::= SEQUENCE {
    channel     TargetId,
    probeId     ProbeId,
    probeType   ProbeType,
    probeModule PrintableString,
    binaryData  FileData  
}

ProbeFetch  ::= SEQUENCE {
    channel     TargetId,
    probe       ProbeId,
    probeType   ProbeType,
    probeValue  ProbeValue
}

-- complete avec le tracker.hrl records finaux
TargetInfo  ::= SEQUENCE {
    channel     TargetId,
    properties  Properties,
    type        TargetInfoType
}

CommandResponce ::= SEQUENCE {
    cmdId       CommandId,
    cmdMsg      CommandMsg
}

---------------------------------------
-- FROM CLIENT
---------------------------------------
TargetCreate    ::= SEQUENCE {
    ipAdd       IpAdd,
    hostname    TargetHostname,
    sysName     TargetSysname,
    permConf    PermConf,
    cmdId       CommandId
}

ProbeCreate     ::= SEQUENCE {
    target      TargetId,
    probeConf   ProbeConf
}

-- TODO server API
TargetUpdate    ::= SEQUENCE {
    target      TargetId
}

TargetDelete    ::= SEQUENCE {
    target      TargetId
}


ProbeUpdate     ::= SEQUENCE {
    target      TargetId,
    probe       ProbeId
}

ProbeDelete     ::= SEQUENCE {
    target      TargetId,
    probe       ProbeId
}



---------------------------------------
-- FULL PDU
---------------------------------------

TrackerPDU ::= CHOICE {
    fromServer  [0] CHOICE {
        targetInfo      [1] TargetInfo,
        probeInfo       [2] ProbeInfo,
        probeFetch      [3] ProbeFetch,
        probeDump       [4] ProbeDump,
        cmdResp         [5] CommandResponce,
        probeModInfo    [6] ProbeModuleInfo,
        probeActivity   [7] ProbeActivity,
        probeReturn     [8] ProbeReturn
    },
    fromClient  [1] CHOICE {
        createTarget    [1] TargetCreate,
        updateTarget    [2] TargetUpdate,
        deleteTarget    [3] TargetDelete,
        createProbe     [4] ProbeCreate,
        updateProbe     [5] ProbeUpdate,
        deleteProbe     [6] ProbeDelete
    }
}

END
