NmsPDU DEFINITIONS IMPLICIT TAGS ::=
-- Use the DEFINITIONS EXPLICIT TAGS in your definition file.
-- * define tags in CHOICE constructs
-- * do not define tags in SEQUENCE constructs
-- * do not use SET constructs

BEGIN

IMPORTS 
    SupercastPDU    FROM ModSupercast
    MonitorPDU      FROM ModMonitor
    LocatorPDU      FROM ModLocator;

PDU ::= CHOICE {
    modSupercastPDU [0] SupercastPDU,
    modMonitorPDU   [2] MonitorPDU,
    modLocatorPDU   [3] LocatorPDU
}

END
